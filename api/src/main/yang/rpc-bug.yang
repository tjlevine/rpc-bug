module rpc-bug {
    yang-version 1;
    namespace "urn:opendaylight:params:xml:ns:yang:rpc-bug";
    prefix "rpc-bug";

    revision "2015-01-05" {
        description "Initial revision of rpc-bug model";
    }

    rpc noop {
        input {}
        output {}
    }
}
